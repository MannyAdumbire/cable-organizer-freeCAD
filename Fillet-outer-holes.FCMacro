# Rough snippet for selecting all outer edges of the organizer for fillet
import math
doc=FreeCAD.ActiveDocument
edgeobjs=[]
edgenames=[]
for count,tedge in enumerate( doc.Body002.Shape.Edges ):
    if( math.isclose(8.0, tedge.Length, rel_tol=1e-3) ):
        edgeobjs.append( tedge )
        edgenames.append( 'Edge' + str(count+1) )

myfillet=doc.Body002.newObject('PartDesign::Fillet')
doc.getObject(myfillet.Label).Radius = 0.500000
doc.getObject(myfillet.Label).Base = (doc.getObject('LinearPattern002'),edgenames )

# doc.getObject('PartDesign__Fillet001').Base = (App.getDocument('ring_clip_cable_organizer').getObject('PolarPattern039'),edgenames[1::2])
